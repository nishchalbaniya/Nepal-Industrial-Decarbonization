# FreeCAD Macro: Parametric model of Rotary Kiln 5000 TPD
# Generated by nepal_decarb_pro v1.0
# Open in FreeCAD: Macro > Macros > Run this file

import FreeCAD
import Part
import Sketcher
import math

# Parameters (all in mm)
L = 72000.0        # length, converted from m
D = 4600.0        # diameter
R = D / 2
T = 50                 # shell thickness
slope_deg = 3.5
slope = math.tan(math.radians(slope_deg))

# Create a new document
doc = FreeCAD.newDocument("KilnModel")
FreeCAD.setActiveDocument("KilnModel")

# Outer cylinder (tilted)
# FreeCAD's Part.makeCylinder takes (radius, height, direction)
# We rotate the cylinder to be tilted
outer = Part.makeCylinder(R, L)
outer.rotate([0, 0, 0], [0, 1, 0], slope_deg)
outer.translate(FreeCAD.Vector(0, 0, 0))
Part.show(outer, "Kiln_Shell_Outer")

# Inner cylinder (refractory inside)
inner = Part.makeCylinder(R - T, L - 50)
inner.rotate([0, 0, 0], [0, 1, 0], slope_deg)
Part.show(inner, "Kiln_Shell_Inner")

# Subtract inner from outer to get hollow shell
shell = outer.cut(inner)
Part.show(shell, "Kiln_Shell")

# Refractory layer
ref_outer = Part.makeCylinder(R - 5, L - 25)
ref_outer.rotate([0, 0, 0], [0, 1, 0], slope_deg)
refractory = ref_outer.cut(Part.makeCylinder(R - T - 5, L - 25).rotate([0, 0, 0], [0, 1, 0], slope_deg))
Part.show(refractory, "Refractory_Lining")

# Tires (riding rings) — 2 supports
for i, x_pos in enumerate([0.15, 0.85]):
    x = L * x_pos
    tire = Part.makeCylinder(R * 1.08, 200)
    tire.rotate([0, 0, 0], [0, 1, 0], slope_deg)
    tire.translate(FreeCAD.Vector(x, 0, 0))
    Part.show(tire, f"Tire_{i+1}")

# Recompute
doc.recompute()
FreeCAD.Gui.SendMsgToActiveView("ViewFit")
FreeCAD.Console.PrintMessage("Kiln model generated.\nL = {} m\nD = {} m\n".format(72.0, 4.6))
